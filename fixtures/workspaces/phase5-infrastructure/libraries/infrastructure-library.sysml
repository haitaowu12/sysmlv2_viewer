package InfrastructureLibrary {
    item def TelemetryFrame;
    item def ControlCommand;
    port def TelemetryPort;
    port def CommandPort;

    part def ControlCentre;
    part def RemoteStation;
    part def NetworkCarrier;
}
