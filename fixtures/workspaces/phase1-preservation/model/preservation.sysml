/* Comments, whitespace, Unicode, and unsupported content must survive: ⚙️ */
package PreservationProbe {
    // Intentionally future/unknown syntax is inventory-only in this fixture.
    experimental future construct { raw := "αβγ"; }
}
